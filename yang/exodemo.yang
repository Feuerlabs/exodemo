module exodemo {

    namespace "http://feuerlabs.com/exodemo";
    prefix demo;

    import exosense {
        prefix exo;
    }

    description "RPC Spec for Exosense Device demo application";

    typedef id-string {
      description "Common type for string identifiers in exodm";
      type string {
	length "1..64";
      }
    }

    //
    // Beep the on-board buzzer
    // Server -> Device
    //
    rpc beep {
        description
	    "Sent from Server to Device. Beep the on-board buzzer, " +
	    "turn on the LED, or a similar visible operation.";

        input {
            uses exo:std-request;

	    leaf duration {
                description
                "Number of milliseconds to run the buzzer for.";
		type uint32;
            }
        }

        // Output only contains status.
        output {
            description
            "Output sent in response to a beep request";

            uses exo:std-callback;
        }
    }


    //
    // Hello ping sent from Device to Server.
    //
    rpc hello {
        description
        "Process a batch of waypointes.";

        input {
            uses exo:std-request;

	    leaf arg1 {
                description  "A dummy argument.";
		type string;
	    }
        }

        // Output only contains status.
        output {
            description
            "Output sent in response to a process-waypoints";
            leaf result {
		type exo:status-code;
	    }
        }
    }


    //
    // Set the interval to elapse between each 'hello' sent
    // from the device to the server.
    //
    rpc set-hello-interval {
        description
	    "This call specifies the number of seconds to elapse between each 'hello' RPC "+
	    "sent from the client to the server. The set-hello-interval RPC is sent from " +
	    "the server to the device.";

        input {
            uses exo:std-request;

	    leaf Interval {
		description "The interval, in seconds, between each 'hello' RPC sent to the server.";
		type uint32;
	    }
        }

        // Output only contains status.
        output {
            description
            "Output sent in response to a process-logdata";
            leaf result {
		type exo:status-code;
	    }
        }
    }
}
